# Sample Requirements
Sample ReqIF document for integration testing

# Specification: Sample Specification

## obj-001: First requirement title
Description of first requirement

## obj-002: Second requirement title
Description of second requirement
