# Nin1_LEB_HL_LAH_Basis

# Specification: Nin1_LEB_HL_LAH_Basis

## 19250151: Allgemeines
- Text übersetzt: General

### 19250152
Hinweise zur KSU Klassifizierung:
Die KSU Klassifizierungen sind gemäß ORL24 Aufbewahrung von Unterlagen (Anlage "Klassifizierungssystematik für Unterlagen (KSU)") festzulegen:
- Temporäre Arbeitsunterlagen / Ausleitungen aus RM-Tool: "Initialklasse" KSU 0.1
- Alle freigegebenen Lastenheftstände: "Produktiventwicklungsunterlagen" KSU 5.1
Achtung: in AVW muss das Dokument vor Freigabe den Status KSU 5.1 haben!
- Der finale Lastenheftstand, welcher die Bauteilanforderungen für das Serienprodukt beschreibt: "Freigaben/dokumentationspflichtige Unterlagen für das Serien-/Endprodukt" KSU 5.3
- Text übersetzt: Notes on the Classification System for Documents (CSD):
  The CSD categories must be defined as per the Organizational Guideline ORL24 "Retention of Documents" (annex "Classification System for Documents (CSD)").
  - Temporary working documents / exports from RM tool: "Initial category" CSD 0.1
  - All released Performance Specification versions: "Product development documents" CSD 5.1
  Important note: In AVW, the document must have CSD 5.1 before it can be released!
  - The final Performance Specification version that specifies the part requirements for the series production product: "Releases and mandatory documentation for series and end products" CSD 5.3
- Status Lieferant A: Klärungsbedarf
- Kommentar Lieferant A: OK

### 19250155
Bei einer Ausleitung des Dokumentes in Word oder Excel, ist die KSU-Klassifizierung selbstständig durch den Autor in der Fußzeile des Word- bzw. Excel-Dokumentes anzupassen.
- Text übersetzt: When exporting the document to Word or Excel, the author must independently adapt the CSD category in the footer of the Word or Excel document.
- Status Lieferant A: akzeptiert
- Kommentar Lieferant A: to be clarified

### 19250157
Arbeitsstände dieses Dokuments sind bei Ausleitungen mit KSU 0.1 (max. 2 Jahre ab Erstellung) zu klassifizieren. Die Klassifizierung erfolgt gemäß ORL24 "Aufbewahrung von Unterlagen".
- Text übersetzt: When exporting working versions of this document, these versions must be classified with CSD 0.1 (max. 2 years from creation). Classification is based on ORL24 "Retention of Documents."
- Status Lieferant A: akzeptiert mit Kommentar
- Kommentar Lieferant A: test png
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
## 19250158: Vorwort
- Text übersetzt: Preface

### 19250159
Die vom Auftragnehmer zu erfüllenden Anforderungen sind im Attribut "Kategorie" grundsätzlich mit dem Eintrag "funktionale Anforderung" oder "nicht-funktionale Anforderung" gekennzeichnet. Elemente mit dem Eintrag "Information", sind Informationen zum besseren Verständnis des BT-LAH. Gibt es keinen Eintrag im Attribut "Kategorie", handelt es sich ebenfalls um eine Anforderung.
- Text übersetzt: Elements, marked with "Funktionale Anforderung" or "Nicht-funktionale Anforderung" in the attribute "Kategorie", are requirements the contractor must fulfill. Elements marked with "Information" contain information about the Performance Specification. If the attribute "Kategorie" is not filled, then this element is also a requirement.
